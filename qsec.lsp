(defun getVariantProperty (vla-objet property) 
  (vlax-safearray->list 
    (variant-value (vlax-get-property vla-objet property))
  )
)

(defun printSecProp (secproplist / index outstring val) 
  (setq index 0)
  (setq outstring "\n")
  (while (< index (length secproplist)) 
    (setq val (nth index secproplist))
    (setq outstring (strcat outstring (car val) ":\t" (rtos (cdr val) 2 2) "\n"))
    (setq index (1+ index))
  )
  (princ outstring)
  (princ)
)

(defun c:QSEC (/ sec area perimeter cx cy ix Iy Ixy Iu Iv r ry secprop) 
  (setq sec (ssname (ssget w) 0))
  (setq sec (vlax-ename->vla-object sec))
  (setq area (vlax-get-property sec 'Area))
  (setq perimeter (vlax-get-property sec 'Perimeter))
  (setq cx (car (getVariantProperty sec 'Centroid)))
  (setq cy (nth 1 (getVariantProperty sec 'Centroid)))
  (command "ucs" (list cx cy) "")
  (setq Ix (car (getVariantProperty sec 'MomentOfInertia)))
  (setq Iy (nth 1 (getVariantProperty sec 'MomentOfInertia)))
  (setq Ixy (vlax-get-property sec 'ProductOfInertia))
  (setq Iu (car (getVariantProperty sec 'PrincipalMoments)))
  (setq Iv (nth 1 (getVariantProperty sec 'PrincipalMoments)))
  (setq rx (car (getVariantProperty sec 'RadiiOfGyration)))
  (setq ry (nth 1 (getVariantProperty sec 'RadiiOfGyration)))
  (setq secprop (list 
                  (cons "A" area)
                  (cons "P" perimeter)
                  (cons "Cx" cx)
                  (cons "Cy" cy)
                  (cons "Ix" Ix)
                  (cons "Iy" Iy)
                  (cons "Ixy" Ixy)
                  (cons "rx" rx)
                  (cons "ry" ry)
                  (cons "Iu" Iu)
                  (cons "Iv" Iv)
                )
  )
  (command "ucs" "w" "")
  (printSecProp secprop)
) ;defun
(princ)
